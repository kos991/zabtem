TEST-SWITCH-MINIMAL-MIB DEFINITIONS ::= BEGIN

IMPORTS
    OBJECT-TYPE, Integer32
        FROM SNMPv2-SMI;

testSwitchObjects OBJECT IDENTIFIER ::= { 1 3 6 1 4 1 55555 1 }

testFanStatus OBJECT-TYPE
    SYNTAX      INTEGER { ok(1), failed(2) }
    MAX-ACCESS  read-only
    STATUS      current
    DESCRIPTION "Self-made fixture object for fan status."
    ::= { testSwitchObjects 1 }

testTemperature OBJECT-TYPE
    SYNTAX      Integer32
    MAX-ACCESS  read-only
    STATUS      current
    DESCRIPTION "Self-made fixture object for switch temperature."
    ::= { testSwitchObjects 2 }

END
